module draft-relation-common {

    yang-version 1.1;
    namespace "urn:ietf:params:xml:ns:yang:draft-relation-common";
    prefix "dr-rel-common";

    import draft-template {
        prefix dr-tmp;
    }

    organization
        "INSA Lyon";

    contact
        "Editor:   Vivekananda Boudia
        <mailto:vivekananda.boudia@insa-lyon.fr>";

    description
        "template common attributes";

    revision 2025-03-09 {
        description
            "Initial revision";
        reference
            "";
    }

    grouping relation-external-ref-common-attr {
        description "common attributes for relations";
        leaf template-ref {
            type leafref {
                path "/dr-tmp:template/dr-tmp:template/dr-tmp:template-id";
            }
            description "reference to template";
        }
        leaf-list request-type-supported {
            type identityref {
                base dr-tmp:request-type;
            }
            description "template is generic and may include requests that are not supported by the network element
            here, we specify the types of requests that the network element supports
            if network element supports all template ALL-REQUEST may be used";
        }
        leaf path {
            type string;
            description "network element can be augmented and may contain containers nested within other containers.
            path is used for filtering.";
        }
        list parameter-value {
            key "param-ref request-type";
            description "parameter value from network element";
            leaf param-ref {
                type leafref {
                    path "/dr-tmp:template/dr-tmp:template/dr-tmp:parameter/dr-tmp:param-id";
                }
                description "reference to template parameter";
            }
            leaf request-type {
                type identityref{
                    base dr-tmp:request-type;
                }
                description "value can be different depending on the request";
            }
            leaf value {
                type string;
                description "value of the parameter";
            }
        }
        container extra {
            description "use for augmentation";
        }

    }

}
