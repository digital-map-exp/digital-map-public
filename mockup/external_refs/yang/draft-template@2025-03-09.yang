module draft-template {

    yang-version 1.1;
    namespace "urn:ietf:params:xml:ns:yang:draft-template";
    prefix "dr-tmp";

    import ietf-inet-types {
        prefix inet;
        reference
            "RFC 6991: Common YANG Data Types";
    }

    organization
        "INSA Lyon";

    contact
        "Editor:   Vivekananda Boudia
        <mailto:vivekananda.boudia@insa-lyon.fr>";

    description
        "template yang model";

    revision 2025-03-09 {
        description
            "Initial revision";
        reference
            "";
    }

    identity template-type {
        description "base identity for template type";
    }

    identity CONFIG {
        base template-type;
        description "template used to retrieve configuration data";
    }

    identity STATE {
        base template-type;
        description "template used to retrieve operational state data";
    }

    identity extra-label {
        description "base identity for extra label";
    }

    identity request-type{
        description "base identity for request type";
    }

    identity ALL_REQUEST{
        base request-type;
        description "all request";
    }

    identity NETCONF {
        base request-type;
        description "request that retrieves data using the NETCONF protocol";
    }

    grouping netconf-request {
        description "netconf request";
        leaf xpath {
            type string;
            description "netconf xpath for request";
        }
    }

    container template {
        description "template container";
        list template {
            key "template-id";
            description "template list";
            leaf template-id {
                type inet:uri;
                description "uniquely identifies a template";
            }
            leaf description {
                type string;
                description "template description";
            }
            container template-type {
                description "template type
                used for filtering";
                leaf base{
                    type identityref {
                        base template-type;
                    }
                    description "template base
                    used for filtering";
                }
                leaf is-historical {
                    type boolean;
                    description "check is template is used to get historical data or not
                    used for filtering";
                }
                leaf-list extra-label {
                    type identityref {
                        base extra-label;
                    }
                    description "extra label
                    used for filtering";
                }
            }
            list parameter {
                key "param-id";
                description "list of parameter used by request";
                leaf param-id {
                    type inet:uri;
                    description "uniquely identifies a parameter";
                }
                leaf description {
                    type string;
                    description "parameter description";
                }
            }
            list request {
                key "request-type";
                description "request list";
                leaf request-type {
                    type identityref{
                        base request-type;
                    }
                    description "request type";
                }
                container request-builder {
                    description "request container that allows users to retrieve data
                    parameters must be enclosed in brackets.";

                }
            }
            container extra {
                description "use for augmentation";
            }
        }
    }

    augment "/template/template/request/request-builder" {
        when "derived-from-or-self(../request-type, 'NETCONF')";
        uses netconf-request;
        description "adding netconf request to possible request";
    }
}
